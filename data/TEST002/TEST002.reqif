# little.pdf_v0

# Specification: little.pdf

## R1: Ich bin ein Heading
- Name: 1.

### R2
Wenn du mit 23 Menschen in einem Raum bist, gibt es eine 50 prozentige Chance, dass zwei am gleichen Tag Geburtstag haben.
